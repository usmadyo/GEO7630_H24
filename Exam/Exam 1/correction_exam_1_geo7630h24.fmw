FME workspace correction_exam_1_geo7630h24.fmw

Parameters:
- SourceDataset_GEOJSON = https://data.montreal.ca/dataset/f8582c4d-a933-4306-bb27-d883e13dd207/resource/7e736f37-c935-4028-8ffe-02e1403c1eaa/download/occupation-commerciale-2022.geojson   # Source GeoJSON File or URL
- SourceDataset_GEOJSON_3 = https://data.montreal.ca/dataset/b628f1da-9dc3-4bb1-9875-1470f891afb1/resource/92cb062a-11be-4222-9ea5-867e7e64c5ff/download/limites-terrestres.geojson   # Source GeoJSON File or URL
- DestDataset_POSTGIS = GEO7630H24   # Connection

Readers:
- GEOJSON_1: GEOJSON from $(SourceDataset_GEOJSON)
- GEOJSON_2: GEOJSON from $(SourceDataset_GEOJSON_3)

Writers:
- POSTGIS_1: POSTGIS to $(DestDataset_POSTGIS)

OCcupation commerciale 2022 (reader GEOJSON_1)
    attributes: ID string, ORIGINE string, T_COMMERCE string, DATE_RECENSEMENT string, CIVIQUE string, TYPE_VOIE string, LIEN_VOIE string, NOM_VOIE string, ORIENTATION string, ADRESSE string, SUITE string, CODE_POST string, ETAGE string, NOM_CENTRE string, NOM_ETAB string, ID_USAGE1 string, USAGE1 string, ID_USAGE2 string, USAGE2 string, ID_USAGE3 string, USAGE3 string, SCIAN string, SITEWEB string, SITE_TRANSACTIONNEL string, ACCES_MOBILITE_REDUITE string, VACANT_A_LOUER string, A_LOUER_CONTACT string, A_LOUER_TELEPHONE string, ARRONDISSEMENT string, QUARTIER string,
      SDC_NOM string, SECTEUR_PME string, ENFANT string, MULTIUSAGE string, MULTIOCCUPANT string, NEQ string, SUFFIXE_NEQ string, COORDX string, COORDY string, LAT string, LONG string
    -> AttributeFilter
limites-terrestres (reader GEOJSON_2)
    attributes: DefaultAtt string
    -> Reprojector_2

Bookmark: FILTRE SUR LES ATTRIBUTS VACANTS
AttributeFilter
    ATTR_NAME = USAGE1
    ATTR_VALUES = <Empty>,<Missing>,<Null>,<Unfiltered>,VACANT
    VACANT -> VertexCreator

Bookmark: Création des points de commerces vacants
Note: Piege il faut créer les entités via le vertex creator
VertexCreator
    MEASURE_TYPE = Continuous
    MODE_NAME = Replace with Point
    XVAL = @Value(LONG)
    YVAL = @Value(LAT)
    -> EsriReprojector_2
    <REJECTED> -> VertexCreator__Rejected_
EsriReprojector_2
    DEST = ESRIWKT|WGS_1984_Web_Mercator_Auxiliary_Sphere|PROJCS["WGS_1984_Web_Mercator_Auxiliary_Sphere",GEOGCS["GCS_WGS_1984",DATUM["D_WGS_1984",SPHEROID["WGS_1984",6378137.0,298.257223563]],PRIMEM["Greenwich",0.0],UNIT["Degree",0.0174532925199433]],PROJECTION["Mercator_Auxiliary_Sphere"],PARAMETER["False_Easting",0.0],PARAMETER["False_Northing",0.0],PARAMETER["Central_Meridian",0.0],PARAMETER["Standard_Parallel_1",0.0],PARAMETER["Auxiliary_Sphere_Type",0.0],UNIT["Meter",1.0]]
    GEOTRANSFORMATION_NAME = <None>
    INTERPOLATION_TYPE_NAME = Nearest Neighbor
    RASTER_CELL_SIZE = Preserve Cells
    RASTER_TOLERANCE = 0.0
    SOURCE = ESRIWKT|GCS_WGS_1984|GEOGCS["GCS_WGS_1984",DATUM["D_WGS_1984",SPHEROID["WGS_1984",6378137.0,298.257223563]],PRIMEM["Greenwich",0.0],UNIT["Degree",0.0174532925199433]]
    REPROJECTED -> PointOnAreaOverlayer [POINT]
VertexCreator__Rejected_: Logger
    LOG_FEATURE = LOG_ONLY
    MAXCOORDS = 20
    MAXFEATS = 20
    MESSAGE = Feature is:
    SEVERITY = INFO

Bookmark: PIEGE JE REPROJETTE EN 4326 CAR H3 PREND SEULEMENT LE 4326
Note: Piège le h3 indexne prend seulement que le 4326 en entrée
Reprojector_2
    DEST = EPSG:4326
    INTERPOLATION_TYPE_NAME = Nearest Neighbor
    RASTER_CELL_SIZE = Preserve Cells
    RASTER_TOLERANCE = 0.0
    REPROJECTED -> H3HexagonalIndexer

Bookmark: H3 INDEXER FILL WITH HEX
H3HexagonalIndexer
    INDEX_OPERATION = Filling Indexes
    -> EsriReprojector_3
    <REJECTED> -> H3HexagonalIndexer__Rejected_
EsriReprojector_3
    DEST = ESRIWKT|WGS_1984_Web_Mercator_Auxiliary_Sphere|PROJCS["WGS_1984_Web_Mercator_Auxiliary_Sphere",GEOGCS["GCS_WGS_1984",DATUM["D_WGS_1984",SPHEROID["WGS_1984",6378137.0,298.257223563]],PRIMEM["Greenwich",0.0],UNIT["Degree",0.0174532925199433]],PROJECTION["Mercator_Auxiliary_Sphere"],PARAMETER["False_Easting",0.0],PARAMETER["False_Northing",0.0],PARAMETER["Central_Meridian",0.0],PARAMETER["Standard_Parallel_1",0.0],PARAMETER["Auxiliary_Sphere_Type",0.0],UNIT["Meter",1.0]]
    GEOTRANSFORMATION_NAME = <None>
    INTERPOLATION_TYPE_NAME = Nearest Neighbor
    RASTER_CELL_SIZE = Preserve Cells
    RASTER_TOLERANCE = 0.0
    SOURCE = ESRIWKT|GCS_WGS_1984|GEOGCS["GCS_WGS_1984",DATUM["D_WGS_1984",SPHEROID["WGS_1984",6378137.0,298.257223563]],PRIMEM["Greenwich",0.0],UNIT["Degree",0.0174532925199433]]
    REPROJECTED -> PointOnAreaOverlayer [AREA]
H3HexagonalIndexer__Rejected_: Logger
    LOG_FEATURE = LOG_ONLY
    MAXCOORDS = 20
    MAXFEATS = 20
    MESSAGE = Feature is:
    SEVERITY = INFO

Bookmark: Jointure et compte spatial comme vu en cours et en lab
PointOnAreaOverlayer
    DEAGGREGATE_INPUT = Yes
    OV_ATTR = _overlaps
    POLYS_FIRST = YES
    AREA -> VOTRECODEMS (writer POSTGIS_1)
    <REJECTED> -> PointOnAreaOverlayer__Rejected_
PointOnAreaOverlayer__Rejected_: Logger
    LOG_FEATURE = LOG_ONLY
    MAXCOORDS = 20
    MAXFEATS = 20
    MESSAGE = Feature is:
    SEVERITY = INFO

Bookmark: Écriture POSTIGS dans la BD
VOTRECODEMS (writer POSTGIS_1)
    attributes: defaultatt text, _h3index numeric(20,0), _overlaps int8
